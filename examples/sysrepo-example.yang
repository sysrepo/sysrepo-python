module sysrepo-example {
  yang-version 1.1;
  namespace "urn:sysrepo:example";
  prefix p;

  feature turbo;

  grouping data {
    container system {
      leaf hostname {
        type string;
      }
    }
    container network {
      list interface {
        ordered-by user;
        key name;
        leaf name {
          type string;
        }
        leaf up {
          type boolean;
        }
        leaf address {
          type string;
        }
        leaf speed {
          if-feature turbo;
          type uint64;
        }
      }
    }

  }

  container conf {
    uses data;

    container security {
      list alarm {
        key name;
        leaf name {
          type string;
        }
        action trigger {
          input {
            leaf duration {
              type uint16;
              units "seconds";
              default 1;
            }
          }
          output {
            leaf message {
              type string;
            }
          }
        }
      }
    }
  }

  container state {
    config false;
    uses data {
      augment 'network/interface' {
        container stats {
          leaf rx {
            type uint64;
          }
          leaf tx {
            type uint64;
          }
        }
      }
    }
    notification state-changed {
      leaf message {
        type string;
      }
    }
  }

  rpc poweroff {
    input {
      leaf behaviour {
        type enumeration {
          enum bad-output;
          enum failure;
          enum success;
        }
      }
    }
    output {
      leaf message {
        type string;
      }
    }
  }

  notification alarm-triggered {
    leaf description {
      type string;
    }
    leaf severity {
      type uint32;
    }
  }
}
